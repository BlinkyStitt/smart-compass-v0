"""Native rear-control component fixtures; not complete enclosure acceptance.

SC_CAD_DIR chooses sources; SC_CONTROL_CHECK_RESULT must name a new evidence
file and closes this isolated FreeCAD process. Without it, leave the UI open.
"""
import hashlib,json,sys,traceback,os
from pathlib import Path
import FreeCAD as App
import Part
from PySide import QtCore
source=Path(os.environ.get('SC_CAD_DIR',Path(__file__).resolve().parent))
result_path=os.environ.get('SC_CONTROL_CHECK_RESULT')
sys.path.insert(0,str(source))
try:
 import control_fixture
 import solid_clearance
 if result_path and Path(result_path).exists():raise ValueError('Choose a new result file; preserve previous evidence')
 paths=[source/name for name in ('control_fixture.py','solid_clearance.py','hardware_spec.py','component-inventory.json','electrical-design.json','electrical_design.py','RearControlsCheck.FCMacro','control-mounts.md','test_control_fixture.py')]
 from electrical_design import CRITICAL_PARTS
 selected=json.loads((source/'electrical-design.json').read_text())['parts']
 if any(selected[n]['part']!=CRITICAL_PARTS[n] for n in ('S1','START','MODE','ACTION','S1_NUT','S1_WASHER')):raise ValueError('Selected control identity changed')
 for name in ('START','MODE','ACTION'):
  if selected[name]['body_nominal_mm'] != [6,6,control_fixture.START_BODY_HEIGHT] or selected[name]['actuator_height_mm'] != list(control_fixture.START_HEIGHT_LIMITS):raise ValueError('Selected button geometry changed: '+name)
 def snapshot():return {str(p):hashlib.sha256(p.read_bytes()).hexdigest() for p in paths}
 before=snapshot();results={}
 for design,diameter,args,options in [('wide',250,((79,-70),(20,-16),(-18,-16),(-47,-16)),{'switch_rotation_deg':90,'guard_mount_offset_mm':13.5}),('narrow',200,((79,-18),(-5,7.5),(-51,-8),(5,-16)),{})]:
  shapes=control_fixture.native_shapes(*args,design=design,**options)
  rear=Part.makeCylinder(diameter/2,2).fuse(shapes['rear_addition']).cut(shapes['rear_cutout'])
  products={name:shapes[name] for name in control_fixture.product_names(design)}
  products['RearPlate' if design=='wide' else 'RearCover']=rear
  checked=list(products.items())
  for i,(a,sa) in enumerate(checked):
   for b,sb in checked[i+1:]:
    if sa.BoundBox.intersect(sb.BoundBox):
     overlap=sa.common(sb).Volume
     if overlap>1e-5:raise ValueError('Control interference: '+design+' '+a+'/'+b+' '+str(overlap))
  missing_parts=('StartMountScrew0','PowerDisconnectNut','ModeSwitch','ActionBackplate')
  if design=='wide':missing_parts+=('StartCompression1',)
  for missing in missing_parts:
   broken=dict(shapes);del broken[missing]
   try:control_fixture.native_check(broken,checked,design=design)
   except ValueError as e:
    if 'component census differs' not in str(e):raise
   else:raise ValueError('Missing rear control component accepted: '+missing)
  try:control_fixture.native_check({**shapes,'StartSwitch2':shapes['StartSwitch']},checked,design=design)
  except ValueError as e:
   if 'component census differs' not in str(e):raise
  else:raise ValueError('Duplicate START component accepted')
  for installed in ([item for item in checked if item[0]!='ModeSwitch'],[*checked,checked[0]]):
   try:control_fixture.native_check(shapes,installed,design=design)
   except ValueError as e:
    if 'Installed rear control product census differs' not in str(e):raise
   else:raise ValueError('Incomplete or duplicate installed controls accepted')
  results[design]=control_fixture.native_check(shapes,checked,design=design)
  results[design]['volumes_cm3']={name:shape.Volume/1000 for name,shape in checked}
  blocked=[*checked,('ThinFingerObstruction',Part.makeBox(.1,.1,.1,App.Vector(args[1][0]-.05,args[1][1]-.05,-10)))]
  try:control_fixture.native_check(shapes,blocked,design=design)
  except ValueError as e:
   if 'finger approach blocked' not in str(e):raise
  else:raise ValueError('Thin control obstruction accepted')
 # Mathematical lower-bound pruning must return the same exact native min,
 # including thin/touching solids. No component or material name is exempt.
 moving=Part.makeCylinder(1,3)
 fixtures=[Part.makeBox(.1,.1,.1,App.Vector(x,0,z)) for x,z in ((1.01,1),(2,0),(20,20),(0,10),(-4,2))]
 for chosen in (fixtures,fixtures+[Part.makeBox(.01,.01,.01,App.Vector(.5,0,1))]):
  actual=solid_clearance.distance(moving,chosen)
  brute=min(moving.distToShape(other)[0] for other in chosen)
  if abs(actual-brute)>1e-10:raise ValueError('Native distance pruning changed exact minimum')
 if snapshot()!=before:raise ValueError('Control check inputs changed')
 record={'scope':'specified-rear-controls-component-study','inputs':before,'freecad':App.Version(),'checks':results,'pruning_native_equivalence':'pass on positive and thin-touching fixtures; not assembly evidence','installed_assembly':'not checked by this component command','physical_acceptance':'unmeasured'}
 if result_path:
  with Path(result_path).open('x') as out:json.dump(record,out,indent=2);out.write('\n')
 print(json.dumps(record),flush=True)
 print('REAR CONTROLS COMPONENT CHECK PASS',flush=True)
except Exception:traceback.print_exc()
finally:
 for name in list(App.listDocuments()):App.closeDocument(name)
 if result_path:QtCore.QTimer.singleShot(0,QtCore.QCoreApplication.quit)
