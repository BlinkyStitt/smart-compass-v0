"""Isolated build/check process for cad.py. Do not run in an editing session."""
import json
import os
from pathlib import Path
import sys
import traceback

import FreeCAD as App
from PySide import QtCore

source = Path(os.environ['SC_CAD_DIR'])
sys.path.insert(0, str(source))
try:
    stage = os.environ['SC_CAD_STAGE']
    if stage == 'build':
        import build
        build.build()
    elif stage == 'check':
        import check
        check.check()
    elif stage == 'demo':
        import demo_export
        demo_export.export()
    else:
        raise ValueError('Unknown CAD stage: ' + stage)
    Path(os.environ['SC_CAD_RESULT']).write_text(json.dumps({
        'stage': stage, 'freecad_version': App.Version(),
    }))
except Exception:
    traceback.print_exc()
finally:
    # These are disposable build documents; their outputs are already saved.
    # View-state changes can mark them dirty and open a modal save prompt.
    for name in list(App.listDocuments()):
        App.closeDocument(name)
    QtCore.QTimer.singleShot(0, QtCore.QCoreApplication.quit)
