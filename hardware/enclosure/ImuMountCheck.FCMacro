"""Verify source-hole IMU mounts; retain physical and installed-assembly limits."""
import hashlib
import json
import os
from pathlib import Path
import sys
import traceback
import FreeCAD as App
from PySide import QtCore

source=Path(os.environ['SC_CAD_DIR']) if 'SC_CAD_DIR' in os.environ else Path(__file__).resolve().parent
sys.path.insert(0,str(source))
result_path=os.environ.get('SC_IMU_CHECK_RESULT')
try:
    if result_path and Path(result_path).exists():raise ValueError('Choose a new IMU result path; preserve existing evidence')
    import imu_mount
    paths=[source/name for name in ('imu_mount.py','test_imu_mount.py','electrical_imu.py','electrical_board.py','electrical-design.json','component-inventory.json','hardware_spec.py','fastener_access.py','test_fastener_access.py','imu-mounts.md','ImuMountCheck.FCMacro')]
    paths+=sorted((source/'sources/lsm9ds1-classic').iterdir())
    def snapshot():return {p.relative_to(source.parents[1]).as_posix():hashlib.sha256(p.read_bytes()).hexdigest() for p in paths}
    before=snapshot();results={}
    for design,z,rotation in (('wide',6,0),('narrow',9,90)):
        shapes=imu_mount.native_shapes(z,rotation);results[design]=imu_mount.native_check(shapes,z)
        for name in ('IMUPCB','IMUScrew0','IMUNut3','IMUComponents'):
            broken=dict(shapes);del broken[name]
            try:imu_mount.native_check(broken,z)
            except ValueError as error:
                if 'census' not in str(error):raise
            else:raise ValueError('Missing IMU product/reference accepted: '+name)
        broken=dict(shapes);broken['rear_addition']=shapes['rear_addition'].copy()
        broken['rear_addition'].translate(App.Vector(0,0,-.2))
        try:imu_mount.native_check(broken,z)
        except ValueError as error:
            if 'lacks full bearing' not in str(error):raise
        else:raise ValueError('Floating IMU mounting annuli accepted')
        broken=dict(shapes);broken['IMUScrew0']=shapes['IMUScrew0'].copy()
        broken['IMUScrew0'].translate(App.Vector(0,0,1))
        try:imu_mount.native_check(broken,z)
        except ValueError as error:
            if 'engage the full nut' not in str(error):raise
        else:raise ValueError('An IMU screw that misses full nut engagement was accepted')
    if before!=snapshot():raise ValueError('IMU inputs changed during native checks')
    record={'checks':results,'inputs':before,'freecad_version':App.Version()}
    if result_path:
        with Path(result_path).open('x') as output:json.dump(record,output,indent=2)
    print(json.dumps(record));print('IMU MOUNT COMPONENT CHECK PASS',flush=True)
except Exception:
    traceback.print_exc()
    raise
finally:
    if result_path:QtCore.QTimer.singleShot(0,QtCore.QCoreApplication.quit)
