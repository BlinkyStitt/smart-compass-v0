import json
import os
from pathlib import Path
import sys
import traceback
import FreeCAD as App
from PySide import QtCore

source=Path(os.environ['STACKED_SOURCE'])
sys.path.insert(0,str(source))
sys.path.insert(0,str(source.parents[1]/'hardware/enclosure'))
try:
    import native
    native.build(Path(os.environ['STACKED_OUTPUT']))
    Path(os.environ['STACKED_RESULT']).write_text(json.dumps({'freecad':App.Version(),'complete':True}))
except Exception:
    traceback.print_exc()
finally:
    # These are disposable build documents; their outputs are already saved.
    # View-state changes can mark them dirty and open a modal save prompt.
    for name in list(App.listDocuments()):
        App.closeDocument(name)
    QtCore.QTimer.singleShot(0,QtCore.QCoreApplication.quit)
