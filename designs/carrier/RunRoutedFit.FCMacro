import os
from pathlib import Path
import sys

sys.path.insert(0, os.environ["COMPASS_CARRIER_SOURCE"])

from routed_fit import check

try:
    check(Path(os.environ["COMPASS_CARRIER_OUTPUT"]) / "routed-fit.json")
finally:
    if os.environ.get("COMPASS_CARRIER_CLOSE_AFTER_CHECK") == "1":
        import FreeCADGui

        FreeCADGui.getMainWindow().close()
